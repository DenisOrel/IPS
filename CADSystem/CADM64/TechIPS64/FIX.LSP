(defun C:techdim()
  (if (null set_dim_tech)
    (load "tcmdtxt")
  )
  (if (null c:cmdim)
    (load "lisp/cmdim")
  )
  (C:cmdim)
)
;;;;;;;;;;;
(defun C:TechDimEdit()
  (if (null set_dim_tech)
    (load "tcmdtxt")
  )
  (if (null c:cmdimw)
    (load "lisp/cmdimw")
  )
  (setq dtype "NEW")
  (C:cmdimw)
)
;;;;;;;;;;;
(defun C:Supp&Clamp()
  (setq pr "bs")
  (C:fix)
)
;;;;;;;;;;;
(defun C:Cent&Mand()
  (setq pr "cen")
  (C:fix)
)
;;;;;;;;;;;
(defun C:FIX (/ delta p1 p2 u u1 t1 t2 VOsmode VAttReq CamCount attprim)
  (prov)
  (if (null GetMsg)
    (load "tech_msg")
  )
  (if (not fixel)
    (load "fix_mnu")
  )
  (if (null sgnscale)
    (setq sgnscale 1.0)
  )
  (fixel pr)
  (cond ((= mn_bl_nm "SYMBOL/camchuck3")
         (setq CamCount 3
               mn_bl_nm "SYMBOL/camchuck"
         )
        )
        ((= mn_bl_nm "SYMBOL/camchuck4")
         (setq CamCount 4
               mn_bl_nm "SYMBOL/camchuck"
         )
        )
        (t (setq CamCount 0))
  )
  (setq VAttReq (getvar "ATTREQ"))
  (setvar "ATTREQ" 0)
  (setq VOsmode (getvar "OSMODE"))
  (setvar "OSMODE" 512)
  (initget 1)
  (while (setq p1 (getpoint (GetMsg 30))) ; "Укажите точку привязки знака"
    (if (ssget p1)
      (progn osnap
             (setq t1 (getpoint p1 (GetMsg 32))) ;"\nOrientation? "
             (command "_LINE" t1 "_PER" p1 "")
             (setq t2 (getvar "lastpoint"))
             (command "_ERASE" "_LAST" "")
             (setq u (+ (angle t2 t1) vv))
      )
      (setq u (+ (getangle p1 (GetMsg 31)) vn)) ;"\nOrientation? "
    )
    (setq u1 (/ (* u 180) pi))
    (command "_INSERT" mn_bl_nm p1 sgnscale "" u1)
    (if (= mn_bl_nm "SYMBOL/camchuck")
      (progn (setq attprim (entnext (entlast)))
             (if attprim
               (command "_ATTEDIT" "_Y" "*" "*" "*" attprim "_VALUE" "_R" (itoa CamCount) "_ANGLE" 0 "")
             )
      )
    )
    (if (= rifl 1)
      (command "_INSERT" "SYMBOL/rifl" p1 sgnscale "" (+ u1 180))
    )
    (if (/= sh_bl_nm "")
      (progn (setq p2 (polar p1 u (* 8 sgnscale)))
             (command "_INSERT" sh_bl_nm p2 sgnscale "" (/ (* (+ pi u) 180) pi))
      )
    )
    (if (/= fix_tp "")
      (progn (if (= (strlen mn_bl_nm) 15)
               (setq delta 5)
               (setq delta 10)
             )
             (if (= mn_bl_nm "SYMBOL/camchuck")
               (setq delta 10)
             )
             (if (= (substr mn_bl_nm 11 1) "t")
               (setq p2 (polar p1 (- u (/ pi 4)) (* (+ delta 2) sgnscale)))
               (setq p2 (polar p1 (- u (/ pi 3)) (* delta sgnscale)))
             )
             (setvar "OSMODE" 0)
             (command "_TEXT" "_MIDDLE" p2 (* 3.0 sgnscale) 0 fix_tp)
      )
    )
  )
  (setvar "osmode" VOsmode)
  (setvar "ATTREQ" VAttReq)
  (restore)
  (princ)
)
