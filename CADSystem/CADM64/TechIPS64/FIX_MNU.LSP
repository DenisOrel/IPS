(defun set_fixtp (nn)
  (setq fix_tp (nth nn fix_lst))
  (if (/= fix_tp "")
    (progn (setq x_ic (dimx_tile "rifl_img")
                 y_ic (dimy_tile "rifl_img")
           )
           (start_image "rifl_img")
           (fill_image 0 0 (- x_ic 1) (- y_ic 1) 0)
           (slide_image 0 0 x_ic y_ic "slide/base(rifl)")
           (end_image)
    )
  )
)
(defun set_shape (n)
  (setq sh (nth n pl_lst))
  (if (/= sh "")
    (progn (setq sld_nm (strcat "slide/base(" sh ")"))
           (setq sh_bl_nm (strcat "symbol/" sh))
           (setq x_ic (dimx_tile "shape_img")
                 y_ic (dimy_tile "shape_img")
           )
           (start_image "shape_img")
           (fill_image 0 0 (- x_ic 1) (- y_ic 1) 0)
           (slide_image 0 0 x_ic y_ic sld_nm)
           (end_image)
    )
  )
)
;;;;;;;;;;;;;;;
(defun OnIconClick (IconNum)
  (if (< (+ IconNum (* CurPage 12) -1) CaptCount)
    (progn (setq index_sld IconNum)
           (if PrevIcon
             (mode_tile PrevIcon 4)
           )
           (setq PrevIcon (strcat "icon" (itoa IconNum)))
           (mode_tile PrevIcon 4)
           (if (> (+ CaptCount 1) IconNum)
             (set_tile "descrip" (nth (- (+ IconNum (* CurPage 12)) 1) IconCapt))
             (set_tile "descrip" "")
           )
    )
  )
)
;;;;;;;;;;;;;;;;
(defun DrawImgPage (/ x_ic y_ic ImgCount Count begin i)
  (setq x_ic (dimx_tile "icon1")
        y_ic (dimy_tile "icon1")
  )
  (setq ImgCount (length Slides)
        begin    (* CurPage 12)
  )
  (setq Count 12
        i 0
  )
  (repeat Count
    (start_image (strcat "icon" (itoa (1+ i))))
    (fill_image 0 0 x_ic y_ic -2)
    (end_image)
    (setq i (1+ i))
  )
  (if (> (+ begin Count) ImgCount)
    (setq Count (- ImgCount begin))
  )
  (setq i 0)
  (repeat Count
    (start_image (strcat "icon" (itoa (1+ i))))
    (slide_image 0 0 x_ic y_ic (nth begin SldList))
    (end_image)
    (setq i (1+ i))
    (setq begin (1+ begin))
  )
)
;;;;;;;;;;;;;
(defun next_page ()
  (setq CurPage (1+ CurPage))
  (mode_tile "prev" 0)
  (if (= CurPage (- PageCount 1))
    (mode_tile "next" 1)
  )
  (DrawImgPage)
  (if (< (+ index_sld (* CurPage 12) -1) CaptCount)
    (if PrevIcon
      (mode_tile PrevIcon 4)
    )
    (progn (setq PrevIcon nil) (OnIconClick 1))
  )
)
;;;;;;;;;;;;;
(defun prev_page ()
  (setq CurPage (1- CurPage))
  (mode_tile "next" 0)
  (if (= CurPage 0)
    (mode_tile "prev" 1)
  )
  (DrawImgPage)
  (if PrevIcon
    (mode_tile PrevIcon 4)
  )
)
;;;;;;;;;;;
(defun getIcon (Caption SldList ActList CaptList / dcl_id dcl_res ImgCount i x_ic y_ic)
  (setq dcl_id (load_dialog "ICON4X3"))
  (setq PrevIcon nil)
  (if (not (new_dialog "icon4x3" dcl_id))
    (progn (unload_dialog dcl_id) (exit))
  )
  (setq IconCapt  CaptList
        CaptCount (length CaptList)
        CurPage   0
        Slides    SldList
        index_sld 0
  )
  (setq PageCount (/ (length SldList) 12))
  (if (< PageCount (/ (length SldList) 12.0))
    (setq PageCount (1+ PageCount))
  )
  (mode_tile "prev" 1)
  (if (< PageCount 2)
    (mode_tile "next" 1)
  )
  (set_tile "label" Caption)
  (DrawImgPage)
  (action_tile "next" "(next_page)")
  (action_tile "prev" "(prev_page)")
  (setq dcl_res (start_dialog))
  (unload_dialog dcl_id)
  (setq IconCapt nil
        CaptCount nil
        PrevIcon nil
        Slides nil
  )
  (setq index_sld (+ index_sld (* CurPage 12) -1))
  (if (< dcl_res 1)
    (setq index_sld -1
          CurPage 0
    )
    (eval (car (nth index_sld ActList)))
  )
  (1+ index_sld)
)
;;;;;;;;;;;;;;;;;;;;;
(defun SetParams (tp / i pri)
  (if (= tp "bs")
    (progn (setq sld_$ (list "tech(bsfix)" "tech_UD(bsfix_U)" "tech_UD(bsfix_D)" "tech(bsmov)" "tech_UD(bsmov_U)"
                             "tech_UD(bsmov_D)" "tech(bsfloat)" "tech_UD(bsfloatU)" "tech_UD(bsfloatD)" "tech(bsadj)"
                             "tech_UD(bsadj_U)" "tech_UD(bsadj_D)" "tech(fixsing)" "tech_UD(fixsingU)"
                             "tech_UD(fixsingD)" "tech(fixtwin)" "tech_UD(fixtwinU)" "tech_UD(fixtwinD)" "tech(dscang)"
                             "tech_ch(c3chuck)" "tech_ch(c4chuck)"
                            )
           )
           (setq run_$ (list '((setq tip "bsfix")) '((setq tip "bsfix_U")) '((setq tip "bsfix_D")) '((setq tip "bsmov"))
                             '((setq tip "bsmov_U")) '((setq tip "bsmov_D")) '((setq tip "bsfloat"))
                             '((setq tip "bsfloatU")) '((setq tip "bsfloatD")) '((setq tip "bsadj"))
                             '((setq tip "bsadj_U")) '((setq tip "bsadj_D")) '((setq tip "fixsing"))
                             '((setq tip "fixsingU")) '((setq tip "fixsingD")) '((setq tip "fixtwin"))
                             '((setq tip "fixtwinU")) '((setq tip "fixtwinD")) '((setq tip "dscang"))
                             '((setq tip "camchuck3")) '((setq tip "camchuck4"))
                            )
           )
           (setq help_$ (list (GetMsg 0)))
           (setq i 1)
           (repeat 18 (setq help_$ (append help_$ (list (GetMsg i)))) (setq i (1+ i)))
           (setq help_$ (append help_$ (list (GetMsg 35))))
           (setq help_$ (append help_$ (list (GetMsg 36))))
           (setq pri (getIcon (GetMsg 28) sld_$ run_$ help_$))
    )
    (progn (setq sld_$ (list "tech(cnfix)" "tech(cnrot)" "tech(cnfloat)" "tech(cnfxbk)" "tech(cnrotbk)" "tech(cnflbk)"
                             "tech(oprcil)" "tech(oprrol)" "tech(oprpvd)"
                            )
           )
           (setq run_$ (list '((setq tip "cnfix")) '((setq tip "cnrot")) '((setq tip "cnfloat")) '((setq tip "cnfxbk"))
                             '((setq tip "cnrotbk")) '((setq tip "cnflbk")) '((setq tip "oprcil"))
                             '((setq tip "oprrol")) '((setq tip "oprpvd"))
                            )
           )
           (setq help_$ (list (GetMsg 19)))
           (setq i 20)
           (repeat 8 (setq help_$ (append help_$ (list (GetMsg i)))) (setq i (1+ i)))
           (setq pri (getIcon (GetMsg 29) sld_$ run_$ help_$))
    )
  )
  pri
)
;;;;;;;;;;;;;;;;;;;;;
(defun fixel (tp / el pri ch i dcl_id)
  (if (not icon_any)
    (load "icon_any")
  )
  (if (null GetMsg)
    (load "tech_msg")
  )
  (setq pri (SetParams tp))
  (if (= pri 1)
    (progn (setq el (nth index_sld run_$)) (mapcar 'eval el))
  )
  (setq mn_bl_nm (strcat "SYMBOL/" tip))
  (setq fix_lst (list "P" "" "H" "E" "M" "EM"))
  (setq pl_lst (list "" "shpl" "shsph" "shcil" "shpriz" "shcon" "shromb" "shtri"))
  (setq sh ""
        sh_bl_nm ""
        rifl 0
        fix_tp ""
        sld_nm ""
  )
  (if (= pri 0)
    (exit)
  )
  (setq dcl_id (load_dialog "fix"))
  (setq what_next 3)
  (while (> what_next 2)
    (if (not (new_dialog "fix_mnu" dcl_id))
      (exit)
    )
    (setq ch (substr tip (strlen tip) 1))
    (if (or (= ch "U") (= ch "D"))
      (mode_tile "rifl" 1)
    )
    (if (or (= (substr tip 1 3) "fix") (= (substr tip 1 3) "cam"))
      (mode_tile "fix_type" 0)
      (mode_tile "fix_type" 1)
    )
    (set_tile "fix_mnu" (nth index_sld help_$))
    (if (null sgnscale)
      (setq sgnscale 1.0)
    )
    (set_tile "scale" (rtos sgnscale))
    (action_tile "shape" "(setq sh (nth (atoi $value) pl_lst))")
    (action_tile "rifl" "(setq rifl (atoi $value))")
    (action_tile "fix_type" "(setq fix_tp (nth (atoi $value) fix_lst))")
    (action_tile "scale" "(setq sgnscale (atof $value))")
    (setq what_next (start_dialog))
  )
  (if (= what_next 1)
    (if (/= sh "")
      (setq sh_bl_nm (strcat "symbol/" sh))
    )
    (exit)
  )
  (princ)
)
